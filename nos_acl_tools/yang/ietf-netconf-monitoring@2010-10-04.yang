module ietf-netconf-monitoring {
  namespace "urn:ietf:params:xml:ns:yang:ietf-netconf-monitoring";
  prefix ncm;

  organization "IETF NETCONF (Network Configuration) Working Group";
  description
    "Minimal ietf-netconf-monitoring for 3S-NOS SF schema negotiation.
     Based on RFC 6022. No imports — self-contained for ODL schema build.";

  revision 2010-10-04 {
    description "Initial version.";
  }

  container netconf-state {
    config false;
    description "Contains NETCONF server monitoring information.";

    container schemas {
      description "Contains the list of data model schemas supported.";
      list schema {
        key "identifier version format";
        description "List of data model schemas supported by server.";
        leaf identifier {
          type string;
          description "Identifier to uniquely reference the schema.";
        }
        leaf version {
          type string;
          description "Version of the schema supported.";
        }
        leaf format {
          type string;
          description "The data modeling language the schema is written in (e.g., yang).";
        }
        leaf namespace {
          type string;
          description "The XML namespace defined by the data model.";
        }
        leaf location {
          type string;
          description "One location from which the schema can be retrieved. NETCONF means get-schema RPC.";
        }
      }
    }
  }

  rpc get-schema {
    description "This operation is used to retrieve a schema from the NETCONF server.";
    input {
      leaf identifier {
        type string;
        mandatory true;
        description "Identifier for the schema list entry.";
      }
      leaf version {
        type string;
        description "Version of the schema requested.";
      }
      leaf format {
        type string;
        description "The data modeling language of the schema.";
      }
    }
    output {
      anyxml data {
        description "Contains the schema content.";
      }
    }
  }
}
