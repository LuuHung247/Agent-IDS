module nos-iptables {
  namespace "urn:3snos:iptables";
  prefix nit;

  organization "3S-NOS Secure Framework";
  description
    "YANG model for iptables FORWARD chain management on SONiC-VS.
     Same module loaded by nos-acl-bridge daemon on each LEAF.
     SF gNMI Set targets path /nos-iptables:acl/rule[rule-id=...].
     Bridge translates → ConfigDB DB4 NOS_IPTABLES_RULE|* → iptables FORWARD.";

  revision 2026-04-27 {
    description "Remove ietf-inet-types import; use inline string pattern for IP prefixes";
  }

  container acl {
    description "Root container for nos-acl-bridge managed rules";

    list rule {
      key "rule-id";
      description "An iptables FORWARD rule managed by Secure Framework";

      leaf rule-id {
        type string {
          length "1..64";
          pattern '[a-zA-Z0-9_\-]+';
        }
        description "Unique rule identifier";
      }

      leaf action {
        type enumeration {
          enum ACCEPT { description "Accept packet (-j ACCEPT)"; }
          enum DROP   { description "Drop packet silently (-j DROP)"; }
          enum RETURN { description "Return to calling chain (-j RETURN)"; }
        }
        mandatory true;
        description "iptables target (-j flag)";
      }

      leaf src-ip {
        type string { pattern '\d+\.\d+\.\d+\.\d+/\d+'; }
        description "Source IP prefix (-s flag)";
      }

      leaf dst-ip {
        type string { pattern '\d+\.\d+\.\d+\.\d+/\d+'; }
        description "Destination IP prefix (-d flag)";
      }

      leaf protocol {
        type enumeration {
          enum tcp  { description "TCP (-p tcp)"; }
          enum udp  { description "UDP (-p udp)"; }
          enum icmp { description "ICMP (-p icmp)"; }
          enum all  { description "Match all protocols (no -p flag)"; }
        }
        default all;
        description "IP protocol to match";
      }

      leaf src-port {
        when "../protocol = 'tcp' or ../protocol = 'udp'";
        type uint16 { range "1..65535"; }
        description "Source port (--sport). Only valid for tcp/udp.";
      }

      leaf dst-port {
        when "../protocol = 'tcp' or ../protocol = 'udp'";
        type uint16 { range "1..65535"; }
        description "Destination port (--dport). Only valid for tcp/udp.";
      }

      leaf priority {
        type uint16 { range "1..9999"; }
        default 1000;
        description
          "Insertion priority. < 100 = top (IDS auto-block),
           100-999 = mid, >= 1000 = append.";
      }

      leaf source {
        type enumeration {
          enum manual { description "Manually inserted rule via UI"; }
          enum sdnc   { description "Rule pushed by ONAP SDNC"; }
          enum agent  { description "Rule auto-generated by IDS Agent (DROP only)"; }
        }
        default sdnc;
        description "Origin of this rule. AGENT cert MUST use agent; DROP action only.";
      }

      leaf comment {
        type string { length "0..256"; }
        description "Human-readable comment embedded in iptables (-m comment)";
      }

      leaf ttl-seconds {
        type uint32 { range "0..86400"; }
        default 0;
        description "TTL seconds. 0 = permanent. TTL tracking by caller.";
      }
    }
  }
}
